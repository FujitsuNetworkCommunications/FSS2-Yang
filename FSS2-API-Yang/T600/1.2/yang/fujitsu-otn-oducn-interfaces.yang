module fujitsu-otn-oducn-interfaces {
  yang-version 1;
  namespace "urn:fujitsu:params:xml:ns:yang:interface:oducn";
  prefix oducn;

  import ietf-interfaces {
    prefix if;
  }
  import fujitsu-state-timer {
    prefix st;
  }
  import fujitsu-entity-states {
    prefix entity-states;
  }
  import fujitsu-otn-odu-interfaces {
    prefix odu;
  }
  import fujitsu-equipment {
    prefix eqpt;
  }
  import fujitsu-entity-maintenance-testsignal {
    prefix fujitsu-testsignal;
  }
  import fujitsu-if-type {
    prefix fjift;
  }
  import fujitsu-gcc {
    prefix fujitsuGcc;
  }
  import fujitsu-otn {
    prefix otn;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains YANG definitions 
     for the ODUCn Interfaces.
     
     Copyright (c) 2015 Fujitsu Network Communications, inc.
     All rights reserved. ";

  revision 2018-04-04 {
    description
      "Added ODUC5 and ODUC6 identity.";
  }
  revision 2016-07-22 {
    description
      "Removed operate-dm rpc to fix sanity failures.";
  }
  revision 2015-05-12 {
    description
      "Initial revision.";
  }

  identity oducn-rate-identity {
    description
      "A unique rate identification of the ODUCn.";
  }

  identity ODUC6 {
    base oducn-rate-identity;
    description
      "Identity for an ODUC6";
  }

  identity ODUC5 {
    base oducn-rate-identity;
    description
      "Identity for an ODUC5";
  }

  identity ODUC4 {
    base oducn-rate-identity;
    description
      "Identity for an ODUC4";
  }

  identity ODUC3 {
    base oducn-rate-identity;
    description
      "Identity for an ODUC3";
  }

  identity ODUC2 {
    base oducn-rate-identity;
    description
      "Identity for an ODUC2";
  }

  identity ODUC1 {
    base oducn-rate-identity;
    description
      "Identity for an ODUC1";
  }

  identity otn-monitoring-layer-identity {
    description
      "An identification for OTN monitoring layer.";
  }

  identity otn-section-layer {
    base otn-monitoring-layer-identity;
    description
      "Identity for section layer.";
  }

  identity otn-path-layer {
    base otn-monitoring-layer-identity;
    description
      "Identity for path layer.";
  }

  identity otn-tandem-connection-layer-1 {
    base otn-monitoring-layer-identity;
    description
      "Identity for tandem connection layer 1.";
  }

  identity otn-tandem-connection-layer-2 {
    base otn-monitoring-layer-identity;
    description
      "Identity for tandem connection layer 2.";
  }

  identity otn-tandem-connection-layer-3 {
    base otn-monitoring-layer-identity;
    description
      "Identity for tandem connection layer 3.";
  }

  identity otn-tandem-connection-layer-4 {
    base otn-monitoring-layer-identity;
    description
      "Identity for tandem connection layer 4.";
  }

  identity otn-tandem-connection-layer-5 {
    base otn-monitoring-layer-identity;
    description
      "Identity for tandem connection layer 5.";
  }

  identity otn-tandem-connection-layer-6 {
    base otn-monitoring-layer-identity;
    description
      "Identity for tandem connection layer 6.";
  }

  grouping block-base-ber-threshold {
    leaf degthr {
      type int16 {
        range "-9..2";
      }
      default "0";
      description
        "DEGTHR:Degraded defect one-second Errored Block Count threshold
         DEGTHR specifies the exponent part X of 10^X.";
    }
    leaf degm {
      type int8 {
        range "2..10";
      }
      default "10";
      description
        "DEGM:Degraded defect consecutive one-second monitoring intervals";
    }
  }

  identity occupation-entity {
    description
      "Identification of occupation in MSI";
  }

  identity unallocated {
    base occupation-entity;
    description
      "Identity for unallocated";
  }

  identity allocated {
    base occupation-entity;
    description
      "Identity for allocated";
  }

  grouping opu {
    container opu {
      when "../monitoring-mode != 'not-terminated'";
      description
        "Optical Channel Payload Unit (OPU)";
      leaf payload-type {
        type string {
          length "2";
          pattern "[0-9a-fA-F]*";
        }
        description
          "Payload Type";
      }
      leaf rx-payload-type {
        type string {
          length "2";
          pattern "[0-9a-fA-F]*";
        }
        description
          "Received Payload Type";
      }
      leaf exp-payload-type {
        type string {
          length "2";
          pattern "[0-9a-fA-F]*";
        }
        description
          "Expected Payload Type";
      }
    }
  }

  grouping oducn-attributes {
    description
      "ODUCn attributes (Optical Data Unit)";
    leaf rate {
      type identityref {
        base oducn-rate-identity;
      }
      description
        "rate identity of the ODUCn. 'identityref' is used
         to allow to extend for future higher rates";
    }
    uses entity-states:oper-status;
    uses entity-states:admin-status {
      refine "admin-status" {
        mandatory false;
        default "down";
      }
    }
    leaf ais-pt {
      type enumeration {
        enum "ais" {
          value 0;
        }
        enum "none" {
          value 1;
        }
      }
    }
    leaf circuit-id {
      type string {
        length "0..45";
      }
      description
        "circuit identifier/user label";
    }
    leaf direction {
      type enumeration {
        enum "uni-rx" {
          value 0;
          description
            "unidirectional receive only";
        }
        enum "uni-tx" {
          value 1;
          description
            "unidirectional transmit only";
        }
        enum "bi" {
          value 2;
          description
            "bidirectional";
        }
      }
    }
    uses otn:tti-choice;
    uses block-base-ber-threshold;
    leaf proactive-DM {
      type boolean;
      description
        "enable/disable proactive Delay Measurement";
    }
    list tcm {
      key "layer";
      uses odu:tcm-attributes;
      max-elements "6";
    }
    leaf monitoring-mode {
      type enumeration {
        enum "not-terminated" {
          description
            "Not Terminated: no detection or generation.
             Overhead is passed through the interface transparently in receive direction 
             unless extension is set for erase";
        }
        enum "terminated" {
          description
            "Terminated: detection and generation enabled.
             Overhead is erased (replaced with all zeros) in receive direction, unless
             extension is set to passthrough";
        }
        enum "monitored" {
          description
            "Monitored: detection enabled.
             Overhead is passed through the interface transparently in receive direction 
             unless extension is set for erase";
        }
      }
      description
        "Monitoring mode of the TCM layer";
    }
    uses opu;
  }

  augment "/if:interfaces/if:interface" {
    container oducn {
      when "../if:type = 'fjift:fujitsuOduc'";
      presence "Attribute Nodes for Optical Channel Data Unit (ODUCn)";
      description
        "Optical Channel Data Unit (ODUCn)";
      uses st:state-timer {
        refine "actual-vstimer" {
          config false;
        }
      }
      uses oducn-attributes {
        refine "oper-status" {
          config false;
        }
        refine "opu/rx-payload-type" {
          config false;
        }
      }
      list list-gcc {
        key "gccType";
        description
          " List of GCC0s";
        uses fujitsuGcc:gcc-group;
      }
      uses fujitsu-testsignal:maint-testsignal;
    }
  }
  notification oducn-notif {
    leaf name {
      type leafref {
        path "/if:interfaces/if:interface/if:name";
      }
    }
    container oducn {
      uses st:state-timer;
      uses oducn-attributes;
    }
  }
}
