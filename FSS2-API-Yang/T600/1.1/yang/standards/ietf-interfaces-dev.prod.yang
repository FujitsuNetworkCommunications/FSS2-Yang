module ietf-interfaces-dev.prod {
  namespace "urn:fujitsu:params:xml:ns:yang:ietf-interfaces-dev.prod";
  prefix if-dev.prod;

  import fujitsu-equipment {
    prefix eqpt;
  }
  import ietf-interfaces {
    prefix if;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains the fujitsu system releated deviations,
     
     Copyright (c) 2017 Fujitsu Ltd.
     All rights reserved. ";

  revision 2018-12-03 {
    description
      "Modified AID of ppp and ip over ppp interface";
  }
  revision 2018-11-27 {
    description
      "shelf range is added for interfaces name";
  }
  revision 2018-11-21 {
    description
      "shelf id 201 is added to the pattern string to support redendency shelf";
  }
  revision 2018-11-09 {
    description
      "ODU AID pattern updated";
  }
  revision 2018-08-30 {
    description
      "Added LMP2 to valid if-name list";
  }
  revision 2018-08-23 {
    description
      "ETH port range updated updated from P5";
  }
  revision 2018-08-09 {
    description
      "Adding F200 interface AID patterns support";
  }
  revision 2018-07-13 {
    description
      "Support for PPP interface in T600";
  }
  revision 2018-07-02 {
    description
      "Support for GRE interface in T500/T510";
  }
  revision 2018-04-23 {
    description
      "Adding logical channel upto 6 for odu4 in T600";
  }
  revision 2017-02-15 {
    description
      "Removed circular dependency due to importing the supporting equipment module";
  }
  revision 2016-11-02 {
    description
      "Added support for eth interfaces on C202";
  }
  revision 2016-10-07 {
    description
      "interface name pattern updated";
  }
  revision 2016-10-04 {
    description
      "check added for interface creation on client port";
  }
  revision 2016-09-28 {
    description
      "Changes to create oc interface";
  }
  revision 2016-09-15 {
    description
      " Enabled E1RX and E1TX in T300 ";
  }
  revision 2016-09-08 {
    description
      "Changes to create interfaces on E3 to E10";
  }
  revision 2016-09-02 {
    description
      "eth AID format check added for subport";
  }

  deviation "/if:interfaces/if:interface/if:name" {
    deviate replace {
      type string {
        length "11..19";
        pattern "(otsig|otsi|otuc|oduc|odu|eth|ip|ppp|och|otu|oc|gre){1}-([1-9]|[1-3][0-9]|[4][0-4]|200|201){1}/[0-5]/[0]/(E([1-2]|[1-2][A-Z][X])(\\.[1-6]|:0|:1|\\.[1-2]:0|:1|\\.[1-2]\\.([1-9]|[1][0]){1})?|E([1-9]|[1][0]){1}|(C([1-9]|[1][0-9]|[2][0]):0|:1){1}|C([1-9]|[1][0-9]|[2][0-5])/[1-4]{1}|C([1-9]|[1][0-9]|[2][0]){1}|([1-9]|[1-3][0-9]|[4][0]){1}|([1-9]|[1-2][0-9]|[3][0-8])(\\.[1]|\\.[1]:0|\\.[1]\\.[1-8]){1}|([3][9]|[4][0])(\\.[1]|\\.[1]:0|\\.[1]\\.[1-9]|\\.[1]\\.[1-7][0-9]|\\.[1]\\.[8][0]|\\.[1]\\.[1-9]\\.[1-8]|\\.[1]\\.[1-7][0-9]\\.[1-8]|\\.[1]\\.[8][0]\\.[1-8]){1}|LCN|LCN[1-2](:([1-9]|[1][0-5]){1})?|LMP|LMP2|NEM|P([3-9]|[1-3][0-9]|[4][0-8]){1}){1}";
      }
    }
    deviate add;
  }
}
