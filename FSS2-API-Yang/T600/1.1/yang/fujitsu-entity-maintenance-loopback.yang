module fujitsu-entity-maintenance-loopback {
  namespace "urn:fujitsu:params:xml:ns:yang:entity-maintenance-loopback";
  prefix entity-maintenance-loopback;

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains a entity maintenance loopback action definitions.
     
     Copyright (c) 2015 Fujitsu Ltd.
     All rights reserved. ";

  revision 2015-09-10 {
    description
      "Initial revision.";
  }

  grouping maint-loopback {
    leaf loopback {
      type enumeration {
        enum "disabled" {
          value 0;
          description
            "default state loopback not active";
        }
        enum "enabled" {
          value 1;
          description
            "loopback operated";
        }
      }
      default "disabled";
      description
        "loopback operation and release";
    }
    leaf location {
      //when "../loopback = 'enabled'";
      type enumeration {
        enum "nearEnd" {
          value 0;
          description
            "Loopback location at near-end";
        }
        enum "farEnd" {
          value 1;
          description
            "Loopback location at far-end";
        }
      }
      default "nearEnd";
      description
        "Set Loopback Location.";
    }
    leaf type {
      //when "../loopback = 'enabled'";
      type enumeration {
        enum "fac" {
          value 0;
          description
            "pre-FEC Loopback in the facility direction";
        }
        enum "term" {
          value 1;
          description
            "Loopback in the terminal direction";
        }
        enum "fac2" {
          value 2;
          description
            "post-FEC Loopback in the facility direction";
        }
      }
      default "fac";
      description
        "Set Loopback type (or direction).";
    }
  }
}
