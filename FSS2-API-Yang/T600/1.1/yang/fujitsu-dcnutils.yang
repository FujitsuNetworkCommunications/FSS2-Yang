module fujitsu-dcnutils {
  namespace "urn:fujitsu:params:xml:ns:yang:fujitsu-dcnutils";
  prefix fujitsu-dcnutils;

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module is used to define the RPC calls to 
       1) Dump tcp/udp packets
       2) Flush DNS Cache
     Copyright (c) 2016 Fujitsu Ltd.
     All rights reserved. ";

  revision 2016-10-08;

  rpc tcpdump {
    description
      "Tool to capture the network traffic.";
    input {
      leaf duration {
        type int32;
        mandatory true;
      }
      leaf interface {
        type string;
      }
      leaf port {
        type int16;
      }
    }
    output {
      leaf-list status {
        type string;
      }
    }
  }
  rpc dns-cache-flush {
    description
      "DNS Cache cleared.";
    output {
      leaf-list status {
        type string {
          length "1..max";
        }
      }
    }
  }
}
