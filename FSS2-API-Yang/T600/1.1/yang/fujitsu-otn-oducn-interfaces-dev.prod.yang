module fujitsu-otn-oducn-interfaces-dev.prod {
  namespace "urn:fujitsu:params:xml:ns:yang:interface:oducn-deviation";
  prefix oducn-deviation;

  import ietf-interfaces {
    prefix if;
  }
  import fujitsu-otn-oducn-interfaces {
    prefix oducn;
  }

  revision 2018-10-29 {
    description
      "config property of operational attributes are included in deviate replace instead of deviate add";
  }
  revision 2018-07-26 {
    description
      "Tim-act-enabled not supported";
  }
  revision 2018-05-08 {
    description
      "Added default value for list-gcc";
  }
  revision 2018-04-06 {
    description
      "removed T200 specific from dev and moved to ann files";
  }
  revision 2016-10-07 {
    description
      "Added default value for exp-payload-type";
  }
  revision 2016-09-13 {
    description
      "Added default value for circuit-id";
  }

  deviation "/if:interfaces/if:interface/oducn:oducn/oducn:rate" {
    deviate replace {
      config false;
    }
  }
  deviation "/if:interfaces/if:interface/oducn:oducn/oducn:direction" {
    deviate replace {
      config false;
    }
  }
  deviation "/if:interfaces/if:interface/oducn:oducn/oducn:testPattern" {
    deviate replace {
      type enumeration {
        enum "PRBS31" {
          value 1;
          description
            "PRBS31 with standard mapping per G.709";
        }
      }
    }
    deviate add {
      default "PRBS31";
    }
  }
  deviation "/if:interfaces/if:interface/oducn:oducn/oducn:testsignal-type" {
    deviate replace {
      type enumeration {
        enum "fac" {
          value 0;
          description
            "test signal in the facility direction";
        }
      }
    }
  }
  deviation "/if:interfaces/if:interface/oducn:oducn/oducn:opu/oducn:payload-type" {
    deviate replace {
      type string {
        length "2";
        pattern "[0-9a-fA-F]*|NA";
      }
    }
  }
  deviation "/if:interfaces/if:interface/oducn:oducn/oducn:opu/oducn:exp-payload-type" {
    deviate replace {
      type string {
        length "2";
        pattern "[0-9a-fA-F]*|NA";
      }
    }
  }
  deviation "/if:interfaces/if:interface/oducn:oducn/oducn:ais-pt" {
    deviate replace {
      type enumeration {
        enum "ais" {
          value 0;
        }
      }
    }
    deviate add {
      default "ais";
    }
  }
  deviation "/if:interfaces/if:interface/oducn:oducn/oducn:standard/oducn:ansi" {
    deviate not-supported;
  }
  deviation "/if:interfaces/if:interface/oducn:oducn/oducn:vstimer" {
    deviate not-supported;
  }
  deviation "/if:interfaces/if:interface/oducn:oducn/oducn:actual-vstimer" {
    deviate not-supported;
  }
  deviation "/if:interfaces/if:interface/oducn:oducn/oducn:proactive-DM" {
    deviate not-supported;
  }
  deviation "/if:interfaces/if:interface/oducn:oducn/oducn:tcm" {
    deviate not-supported;
  }
  deviation "/if:interfaces/if:interface/oducn:oducn/oducn:degthr" {
    deviate replace {
      type int16 {
        range "-5..2";
      }
    }
  }
  deviation "/if:interfaces/if:interface/oducn:oducn/oducn:standard/oducn:itu/oducn:tti-itu/oducn:tim-det-mode" {
    deviate replace {
      type enumeration {
        enum "off" {
          value 0;
          description
            "TIM detection off";
        }
        enum "sapi-only" {
          value 1;
          description
            "TIM detection sapi only";
        }
        enum "dapi-only" {
          value 2;
          description
            "TIM detection dapi only";
        }
        enum "sapi-and-dapi" {
          value 4;
          description
            "TIM detection sapi and dapi";
        }
      }
    }
    deviate add {
      default "off";
    }
  }
  deviation "/if:interfaces/if:interface/oducn:oducn/oducn:standard/oducn:itu/oducn:tti-itu/oducn:tim-act-enabled" {
    deviate not-supported;
  }
  deviation "/if:interfaces/if:interface/oducn:oducn/oducn:monitoring-mode" {
    deviate add {
      default "terminated";
    }
  }
  deviation "/if:interfaces/if:interface/oducn:oducn/oducn:opu/oducn:payload-type" {
    deviate add {
      default "22";
    }
  }
  deviation "/if:interfaces/if:interface/oducn:oducn/oducn:opu/oducn:exp-payload-type" {
    deviate add {
      default "22";
    }
  }
  deviation "/if:interfaces/if:interface/oducn:oducn/oducn:circuit-id" {
    deviate add {
      default "";
    }
  }
  deviation "/if:interfaces/if:interface/oducn:oducn/oducn:list-gcc/oducn:gccType" {
    deviate replace {
      type enumeration {
        enum "gcc1" {
          value 1;
          description
            "gcc1";
        }
      }
    }
    deviate add {
      default "gcc1";
    }
  }
}
