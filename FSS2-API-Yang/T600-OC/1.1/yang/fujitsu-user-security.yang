module fujitsu-user-security {
  yang-version 1;
  namespace "urn:fujitsu:params:xml:ns:yang:usersecurity";
  prefix secu;

  import fujitsu-user-security-typedefs {
    prefix usersecu-type;
  }
  import tailf-aaa {
    prefix taa;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains definitions for managment of security feature 
     defaults used for user account provisioning as well as system wide
     security feature settings.
     Copyright (c) 2015 Fujitsu Ltd.
     All rights reserved. ";

  revision 2018-07-18 {
    description
      "Deprecated unused security params";
  }
  revision 2017-12-22 {
    description
      "Crypt password type modified";
  }
  revision 2017-11-06 {
    description
      "Modifies the descriptions for level-2 and level-3 Users";
  }
  revision 2017-10-13 {
    description
      "Added missing help strings for Systemwide Security elements";
  }
  revision 2017-09-27 {
    description
      "deprecated all unused read-write elements from security yang
       and removed all invisible and read-only unused elements";
  }
  revision 2017-07-05 {
    description
      "Security Yang performance improvement";
  }
  revision 2017-06-08 {
    description
      "Added description for Authentication order";
  }
  revision 2017-06-06 {
    description
      "Moved authentication-order precondition from data model";
  }
  revision 2017-05-26 {
    description
      "Added support for configuring Accounting Order";
  }
  revision 2017-05-05 {
    description
      "updated must statement and min-elements under authentication-order 
       to support tacacs or radius only cases";
  }
  revision 2017-03-29 {
    description
      "cli preformat support removed for pre-login-banner and post-login-banner";
  }
  revision 2017-03-20 {
    description
      "Validation check for authentication order";
  }
  revision 2016-11-21 {
    description
      "Updated for configurable banner support";
  }
  revision 2016-11-04 {
    description
      "Modified the type to password-type for each leaf of rpc change-password";
  }
  revision 2015-09-30;

  container security {
    description
      "Security related Configurations";
    container defaults {
      status deprecated;
      leaf uage {
        status deprecated;
        type usersecu-type:uage-type;
        description
          "(Deprecated) Use 'set security systemwide username-minimum-length <>' instead";
        mandatory true;
      }
      leaf page {
        status deprecated;
        type usersecu-type:page-type;
        mandatory true;
        description
          "(Deprecated) Use 'set security systemwide password-minimum-length <>' instead";
      }
      leaf minit {
        status deprecated;
        type usersecu-type:minit-type;
        mandatory true;
      }
      leaf reauth {
        status deprecated;
        type usersecu-type:reauth-type;
        mandatory true;
      }
      leaf idle-timeout {
        status deprecated;
        type uint64 {
          range "0 .. 8192";
        }
        mandatory true;
      }
    }
    container systemwide {
      leaf-list authentication-order {
        description
          "AAA authentication order defines the destination hierarchy for authentication and authorization";
        max-elements "3";
        min-elements 1;
        type usersecu-type:authentication-type;
        ordered-by user;
      }
      leaf-list accounting-order {
        description
          "AAA accounting order defines the destination hierarchy for accounting audit logging";
        max-elements "2";
        type usersecu-type:accounting-type;
        ordered-by user;
      }
      leaf username-minimum-length {
        type usersecu-type:umin-type;
        description
          "Minimum Username length";
      }
      leaf password-minimum-length {
        type usersecu-type:pmin-type;
        description
          "Minimum Password length";
      }
      leaf password-mode {
        type usersecu-type:pcontent-type;
        description
          "Determines the allowed password content - BASIC or ENHANCED";
      }
      leaf pre-login-banner {
        type string {
          length "0..1600";
        }
        default
          "Welcome to the FUJITSU 1FINITY
           Copyright Fujitsu Network Communications";
        description
          "Pre-login banner that is to be displayed before user enters the login
           details";
      }
      leaf post-login-banner {
        type string {
          length "0..1600";
        }
        default "NOTICE: THIS IS A PRIVATE COMPUTER SYSTEM. UNAUTHORIZED ACCESS OR USE MAY LEAD TO PROSECUTION.";
        description
          "Post-login banner that is to be displayed after successful login";
      }
      leaf uage {
        status deprecated;
        description
          "(Deprecated) Systemwide user account aging";
        type usersecu-type:uage-type;
        default "OFF";
      }
      leaf umin {
        status deprecated;
        type usersecu-type:umin-type;
        description
          "(Deprecated) Use 'set security systemwide username-minimum-length <>' instead";
      }
      leaf pmin {
        status deprecated;
        type usersecu-type:pmin-type;
        description
          "(Deprecated) Use 'set security systemwide password-minimum-length <>' instead";
      }
      leaf pcontent {
        type usersecu-type:pcontent-type;
        status deprecated;
        description
          "(Deprecated) Use 'set security systemwide password-mode <>' instead";
      }
      leaf prot {
        status deprecated;
        type usersecu-type:prot-type;
        description
          "(Deprecated) Password Rotation";
      }
      leaf smt {
        status deprecated;
        type usersecu-type:smt-type;
        description
          "(Deprecated) Provides permission to have multiple sessions";
      }
      leaf dural {
        status deprecated;
        type usersecu-type:dural-type;
        description
          "(Deprecated) Duration of account lockout after maximum number of unsuccessful user login attempts";
      }
      leaf maxinv {
        type usersecu-type:maxinv-type;
        status deprecated;
        description
          "(Deprecated) Maximum number of unsuccessful user login attempts before account gets locked out";
      }
      leaf lastlogin {
        status deprecated;
        type usersecu-type:lastlogin-type;
        description
          "(Deprecated) Timestamp of the last login and number of login failures since last successful login";
      }
      leaf warn {
        status deprecated;
        type usersecu-type:warn-type;
        description
          "(Deprecated) Set warning message";
      }
      leaf debug {
        status deprecated;
        type usersecu-type:yORn-type;
        description
          "(Deprecated) Enable Debugging level Message";
      }
    }
  }
  list usergrp {
    description
      "User group related configurations";
    key "group";
    leaf group {
      type usersecu-type:group-type;
    }
    leaf gid {
      type int32;
    }
  }
  list usersec {
    status deprecated;
    description
      "User security related configurations";
    key "username";
    leaf username {
      status deprecated;
      must "/secu:users/secu:user[secu:username=current()]/secu:username = current()" {
        error-message "Entered username must already be provisioned in users.";
      }
      type usersecu-type:username-type;
    }
    leaf uage {
      status deprecated;
      type usersecu-type:uage-type;
    }
    leaf page {
      status deprecated;
      type usersecu-type:page-type;
    }
    leaf pidout {
      status deprecated;
      when "../page != 'OFF'";
      config false;
      type int32;
    }
    leaf minit {
      status deprecated;
      type usersecu-type:minit-type;
    }
    leaf reauth {
      status deprecated;
      type usersecu-type:reauth-type;
    }
    leaf idle-timeout {
      status deprecated;
      type int32;
    }
  }
  container users {
    description
      "Users related configurations";
    must "boolean(/secu:users/secu:user[(secu:group='level-4') and (secu:adminState='allow')] ) or (/secu:users/secu:user[(secu:group='level-6') and (secu:adminState='allow')])" {
      error-message "Atleast one Level-4 or Level-6 user with allow admin state must be present";
    }
    list user {
      max-elements "100";
      key "username";
      leaf username {
        type usersecu-type:username-type;
        mandatory true;
      }
      leaf crypt-password {
        type usersecu-type:crypt-password-type;
      }
      leaf password {
        type usersecu-type:password-type;
      }
      leaf group {
        must "/secu:usergrp[secu:group=current()]/secu:group = current()" {
          error-message "entered group must be level-1, level-2..., or level-6";
        }
        type usersecu-type:group-type;
        mandatory true;
      }
      leaf adminState {
        type usersecu-type:adminState-type;
        default "allow";
      }
    }
  }
  rpc change-password {
    description
      "RPC to change the logged in user's password";
    input {
      leaf currentPassword {
        type usersecu-type:password-type;
        description
          "provide the current password";
        mandatory true;
      }
      leaf newPassword {
        type usersecu-type:password-type;
        description
          "provide a new password";
        mandatory true;
      }
      leaf newPasswordConfirm {
        type usersecu-type:password-type;
        description
          "re-enter the new password ";
        mandatory true;
      }
    }
    output {
      leaf status {
        type enumeration {
          enum "Successful" {
            value 1;
          }
          enum "Failed" {
            value 2;
          }
        }
        mandatory true;
        description
          "Successful or Failed";
      }
      leaf status-message {
        type string;
        description
          "Gives a more detailed reason for success / failure";
      }
    }
  }
}
