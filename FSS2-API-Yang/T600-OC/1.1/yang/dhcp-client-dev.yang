module dhcp-client-dev {
  namespace "urn:fujitsu:params:xml:ns:yang:dhcp-client-dvn";
  prefix dhcp-dvn;

  import dhcp-client {
    prefix dhcp;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains the DHCP Client deviations from Standard IETF Draft.
     
     Copyright (c) 2015 Fujitsu Ltd.
     All rights reserved. ";

  revision 2015-09-11 {
    description
      "Initial Revision";
  }

  deviation "/dhcp:clientv4/dhcp:client-if" {
    deviate not-supported;
  }
  deviation "/dhcp:serverv4" {
    deviate not-supported;
  }
  deviation "/dhcp:relayv4" {
    deviate not-supported;
  }
}
