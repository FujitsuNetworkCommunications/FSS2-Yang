module fujitsu-powerdraw {
  namespace "urn:fujitsu:params:xml:ns:yang:equipment:slot-pwrdraw";
  prefix pwrdraw;

  import fujitsu-equipment {
    prefix eqpt;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains definitions for parameters in Slot Equipment.
     
     Copyright (c) 2017 Fujitsu Ltd.
     All rights reserved. ";

  revision 2017-04-04 {
    description
      "Initial revision.";
  }

  augment "/eqpt:eqpt/eqpt:shelf/eqpt:slot" {
    description
      "This augments parameters for a slot";
    leaf powerDraw {
      type uint16;
      config false;
      description
        "powerDraw is defined as 'PowerDraw'";
    }
  }
}
