module fujitsu-equipment-dev.prod {
  namespace "urn:fujitsu:params:xml:ns:yang:equipment-dev.prod";
  prefix fujitsu-equipment-dev.prod;

  import fujitsu-equipment {
    prefix eqpt;
  }
  import fujitsu-pm-types {
    prefix pm-types;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains the eqpt releated deviations,
     
     Copyright (c) 2015 Fujitsu Ltd.
     All rights reserved. ";

  revision 2018-12-11 {
    description
      "Added PM Threshold to be metered for subport";
  }
  revision 2017-06-27 {
    description
      "Moved must conditions to annotation file";
  }
  revision 2017-01-25 {
    description
      "Added deviation for subport pm-th-high & low";
  }
  revision 2017-01-06 {
    description
      "Added deviation for num-lanes";
  }
  revision 2016-11-03 {
    description
      "Added shelfId 200";
  }
  revision 2016-09-21 {
    description
      " Disabled E1RX and E1TX in Normal shelf mode";
  }
  revision 2016-09-20 {
    description
      " Enabled LMP/LCN port in REGEN";
  }
  revision 2016-09-15 {
    description
      " Enabled E1RX and E1TX in T300 ";
  }
  revision 2016-09-12 {
    description
      "Enabled E2 port on T100 NORMAL mode";
  }
  revision 2016-09-02 {
    description
      "pm threshold data type change.";
  }
  revision 2016-05-16 {
    description
      "Initial revision.";
  }
  revision 2016-11-04 {
    description
      "Added T200 card check to support REGEN mode";
  }

  deviation "/eqpt:eqpt/eqpt:shelf/eqpt:shelfId" {
    deviate replace {
      type string {
        length "1..3";
        pattern "([1-9]|[1-8][0-9]|9[0-4]|10[1-9]|[1][1-8][0-9]|19[0-4]|200|201)" {
          error-message "Shelf number should be 1-94, 101-194 or 200 or 201";
        }
      }
    }
  }
  deviation "/eqpt:eqpt/eqpt:shelf/eqpt:pm" {
    deviate not-supported;
  }
  deviation "/eqpt:eqpt/eqpt:shelf/eqpt:slot/eqpt:pm" {
    deviate not-supported;
  }
  deviation "/eqpt:eqpt/eqpt:shelf/eqpt:slot/eqpt:subslot/eqpt:pm" {
    deviate not-supported;
  }
  deviation "/eqpt:eqpt/eqpt:shelf/eqpt:slot/eqpt:subslot/eqpt:port/eqpt:pm/eqpt:pm-threshold/eqpt:pm-th-metered/eqpt:pm-th-low" {
    deviate replace {
      type decimal64 {
        fraction-digits 2;
      }
    }
  }
  deviation "/eqpt:eqpt/eqpt:shelf/eqpt:slot/eqpt:subslot/eqpt:port/eqpt:pm/eqpt:pm-threshold/eqpt:pm-th-metered/eqpt:pm-th-high" {
    deviate replace {
      type decimal64 {
        fraction-digits 2;
      }
    }
  }
  deviation "/eqpt:eqpt/eqpt:shelf/eqpt:slot/eqpt:subslot/eqpt:port/eqpt:subport/eqpt:pm/eqpt:pm-threshold/eqpt:pm-th-metered/eqpt:pm-th-low" {
    deviate replace {
      type decimal64 {
        fraction-digits 2;
      }
    }
  }
  deviation "/eqpt:eqpt/eqpt:shelf/eqpt:slot/eqpt:subslot/eqpt:port/eqpt:subport/eqpt:pm/eqpt:pm-threshold/eqpt:pm-th-metered/eqpt:pm-th-high" {
    deviate replace {
      type decimal64 {
        fraction-digits 2;
      }
    }
  }
  deviation "/eqpt:eqpt/eqpt:shelf/eqpt:slot/eqpt:subslot/eqpt:port/eqpt:pm/eqpt:pm-threshold/eqpt:pm-type" {
    deviate replace {
      type enumeration {
        enum "metered" {
          value 1;
          description
            "Metered PM type";
        }
      }
    }
  }
  deviation "/eqpt:eqpt/eqpt:shelf/eqpt:slot/eqpt:subslot/eqpt:port/eqpt:subport/eqpt:pm/eqpt:pm-threshold/eqpt:pm-type" {
    deviate replace {
      type enumeration {
        enum "metered" {
          value 1;
          description
            "Metered PM type";
        }
      }
    }
  }
  deviation "/eqpt:eqpt/eqpt:shelf/eqpt:slot/eqpt:subslot/eqpt:port/eqpt:subport/eqpt:pm/eqpt:pm-threshold/eqpt:pm-th-binned" {
    deviate not-supported;
  }
  deviation "/eqpt:eqpt/eqpt:shelf/eqpt:slot/eqpt:subslot/eqpt:port/eqpt:pm/eqpt:pm-threshold/eqpt:pm-th-binned" {
    deviate not-supported;
  }
  deviation "/eqpt:eqpt/eqpt:shelf/eqpt:slot/eqpt:subslot/eqpt:port/eqpt:num-lanes" {
    deviate add {
      default "4";
    }
  }
}
