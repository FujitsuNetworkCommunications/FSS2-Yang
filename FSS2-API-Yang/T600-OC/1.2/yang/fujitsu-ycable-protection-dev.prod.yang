module fujitsu-ycable-protection-dev.prod {
  namespace "urn:fujitsu:params:xml:ns:yang:ycable-deviation";
  prefix ycable-deviation;

  import fujitsu-ycable-protection {
    prefix ypg;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains YANG annotations
     for the OTU Interfaces for T3x0.
     
     Copyright (c) 2017 Fujitsu Network Communications, inc.
     All rights reserved. ";

  revision 2019-02-12 {
    description
      "YPG name is restricted to allow alphanumaric, hyphen, underscore and forward slash";
  }
  revision 2019-01-28 {
    description
      "YPG name is restricted to give alphanumaric, minus and underscore alone";
  }
  revision 2018-01-04 {
    description
      "Initial revision.";
  }

  deviation "/ypg:ycable-protection/ypg:ypg-group/ypg:ypg-interfaces" {
    deviate replace {
      type string {
        pattern "port-([1-9]|[1-3][0-9]|[4][0])/0/0/C([1-9]|[1][0-9]|[2][0])";
      }
    }
  }
  deviation "/ypg:ycable-protection/ypg:ypg-group/ypg:working-if" {
    deviate replace {
      type string {
        pattern "port-([1-9]|[1-3][0-9]|[4][0])/0/0/C([1-9]|[1][0-9]|[2][0])";
      }
    }
  }
  deviation "/ypg:ycable-protection/ypg:ypg-group/ypg:name" {
    deviate replace {
      type string {
        length "1..255";
        pattern "[a-zA-Z0-9_/-]*" {
          error-message "The YPG name allows only alphanumeric, hyphen, underscore and forward slash";
        }
      }
    }
  }
}
