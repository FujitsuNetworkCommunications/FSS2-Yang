module fujitsu-inventory {

     namespace "urn:fujitsu:params:xml:ns:yang:inventory";
     prefix fujitsu-inventory;

     import fujitsu-physical-inventory {
       prefix physical-inventory;
     }


     organization
       "Fujitsu Ltd.";

     contact
       "Fujitsu Network Comminucations, Inc.

        Address: 2801 Telecom Parkway
                 Richardson, Texas 75082

        Tel: +1-800-USE-FTAC (1-800-873-3822)
        Email: ftac@fnc.fujitsu.com
        Web: www.fujitsu.com/us/services/telecom";

     description
       "This module contains the Inventory Operational model for Fujitsu
        Equipment.
        Copyright (c) 2014 Fujitsu Network Comunications, inc. 
        All rights reserved. ";

     revision 2014-12-02 {
       description
         "Initial revision.";
       reference
         "None.";
     }

  list inventory {
    config false; 
    description
        "Inventory of all the equipment currently plugged in";
 
    leaf inventoryName {
      type string;
      description
        "String indicating the location of equipment";
    }
    uses physical-inventory:PhysicalInventory;
  }
}
