module fujitsu-eqpt-operations-dev.prod {
    namespace "urn:fujitsu:params:xml:ns:yang:eqpt-operations-dev.prod";
    prefix fujitsu-eqpt-operations-dev.prod;
 
    import tailf-common { 
        prefix tailf; 
    }
    
    import fujitsu-eqpt-operations {
        prefix oper;
    }

    organization
        "Fujitsu Ltd.";

    contact
        "Fujitsu Ltd.

        Address: 2801 Telecom Parkway
                 Richardson, Texas 75082

        Tel: +1-800-USE-FTAC (1-800-873-3822)
        Email: ftac@fnc.fujitsu.com
        Web: www.fujitsu.com/us/services/telecom";

    description
       "This module contains deviations to the fujitsu equipment operations.
        Copyright (c) 2016 Fujitsu Ltd.
        All rights reserved. ";

    revision 2017-02-28 {
        description
        "SOFT reset is supported for T100. So adding back SOFT entry.";
    }

    revision 2017-02-22 {
        description
        "SOFT reset not supported. So removing entry from CLI.";
    }

    revision 2017-02-01 {
        description
        "Deviated create-pm-log as not supported.";
    }

    revision 2016-12-07 {
        description
        "Added option for SOFT reset";
    }

    revision 2016-07-05 {
        description
        "Initial revision.";
    }    

    deviation "/oper:eqpt-reset/oper:input/oper:reset" {
        deviate replace {
            type enumeration {
                enum HARD {
                    value "0";
                    description "Hard Reset";
                }
                enum SOFT {
                    value "1";
                    description "Soft Reset";
                }
            }
        }
    }

    deviation "/oper:create-pm-log" {
        deviate not-supported;
    }

}
