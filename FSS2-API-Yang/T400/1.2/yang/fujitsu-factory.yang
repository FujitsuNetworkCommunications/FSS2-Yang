module fujitsu-factory {
  namespace "urn:fujitsu:params:xml:ns:yang:fujitsu-factory";
  prefix fujitsu-factory;

  import tailf-common {
    prefix tailf;
  }

    organization
       "Fujitsu Ltd.";

    contact
       "Fujitsu Ltd.

        Address: 2801 Telecom Parkway
                 Richardson, Texas 75082

        Tel: +1-800-USE-FTAC (1-800-873-3822)
        Email: ftac@fnc.fujitsu.com
        Web: www.fujitsu.com/us/services/telecom";

    description
       "used for the debugging of fujitsu.

        Copyright (c) 2015 Fujitsu Ltd.
        All rights reserved. ";

    revision 2015-10-13 {
        description
        "Initial revision.";
    }

   typedef debugPortType {
     type enumeration {
       enum enable {
         value "0";
         description "Enable SSH Debug Port";
       }
       enum disable {
         value "1";
         description "Disable SSH Debug Port";
       }
     }
     description "Reset Types";
   } // debugPortType

   rpc debug-port {
    description
      "Enables SSH Debug Port";
    input {
      leaf status {
         type debugPortType; // Allowed values are enable,disable 
         description " enable  means to true on the debug port";
      }
    } // input
    output {
      leaf status {
        type string {
          length "4..255";
        }
        description
          "response of the command";
      }
    } //output
  } //debug-port

  rpc debug-port-state {
    description
      "debug-port state";
    output {
      leaf port-status {
        type string {
          length "4..255";
        }
        description
          "response of the command";
      }
    } //output
  } //debug-port-state

}
