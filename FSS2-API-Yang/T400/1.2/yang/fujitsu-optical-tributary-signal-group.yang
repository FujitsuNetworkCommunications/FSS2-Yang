//
// Delta from v1.4
// 
// * namespace updated (ot -> otsig)
// * 'otucn-rate-identity' definitions are removed but they are imported from
//   'fujitsu-otn-otucn-interfaces'.
// * type definition for 'cnfmode-type' and 'roadm-type' are moved into their
//   leaf definitions. 
// * The leaf 'circuit-id' is removed.
// * A refine statement to add 'config false' to the leaf 'fec' is added.
// * The IF type 'otnOtsig' is defined in the module
//   'fujitsu-if-type'. Codes changed to import and use it.
//-----
// Delta from v1.5 based on OCT DR @ RICH
// * Default value for the attribute 'hi-performance-fec' is modified.
//   (ON->OFF)
// * A leaf ais-pt is added to specify NW laser behavior as an alarm transfer action.
//

module fujitsu-optical-tributary-signal-group {

    yang-version 1;

    namespace "urn:fujitsu:params:xml:ns:yang:interface:otsig";
    prefix otsig;

    import ietf-interfaces {
        prefix if;
    }

    import fujitsu-state-timer {
        prefix st;
    }

    import fujitsu-entity-states {
        prefix entity-states;
    }

    import fujitsu-if-type {
        prefix fjift;
    }

   organization
       "Fujitsu Ltd.";

   contact
       "Fujitsu Ltd.

        Address: 2801 Telecom Parkway
                 Richardson, Texas 75082

        Tel: +1-800-USE-FTAC (1-800-873-3822)
        Email: ftac@fnc.fujitsu.com
        Web: www.fujitsu.com/us/services/telecom";

    description
       "This module contains YANG definitions 
        for the Optical Transport Interfaces.
        
        Copyright (c) 2015 Fujitsu Network Communications, inc.
        All rights reserved. ";

    revision 2015-04-10 {
        description
        "Initial revision.";
    }


    // definitions of OTUCn rate entities
    //
    identity nw-rate-identity {
        description
            "A unique rate identification of the OTUCn.";
    }

    identity R400G {
        base nw-rate-identity;
        description
            "Identity for 400G NW Rate";
    }
    identity R300G {
        base nw-rate-identity;
        description
            "Identity for 300G NW Rate";
    }
    identity R200G {
        base nw-rate-identity;
        description
            "Identity for 200G NW Rate";
    }
    identity R100G {
        base nw-rate-identity;
        description
            "Identity for 100G NW Rate";
    }

    grouping otsig-attributes {
        
        description "Optical Tributary Signal Group attributes (OTSIG)";

        uses entity-states:oper-status;
        uses entity-states:admin-status {
            refine admin-status {
                mandatory false;
                default down;
            }
        }

        leaf ais-pt {
            type enumeration {
               enum shutdown {
                  value "0";
               }
               enum none {
                  value "1";
               }
            }
        }

        leaf nwrate {                        
            type identityref {               
                base nw-rate-identity;    
            }
            description "network rate";        
        }                                    

        //subcarrier
        leaf subcarrier {
            type uint8 {
                range "1..2";
            }
            description "The number of sub carrier. 
            This Value is decided depending on otucn-rate-identity.";
        }

        leaf modulation-format {
                type enumeration {
                    enum bpsk {
                        value "0";
                        description "binary phase-shift keying";  
                    }
                    enum dc-dp-bpsk {
                        value "1";
                        description "DC dual-polarization binary phase-shift keying";  
                    }
                    enum qpsk {
                        value "2";
                        description "quadrature phase-shift keying";  
                    }
                    enum dp-qpsk {
                        value "3";
                        description "dual-polarization binary phase-shift keying";  
                    }
                    enum qam16 {
                        value "4";
                        description "quadrature amplitude modulation 16";  
                    }
                    enum dp-qam16 {
                        value "5";
                        description "dual-polarization quadrature amplitude modulation 16";  
                    }
                    enum dc-dp-qam16 {
                        value "6";	
                        description "DC dual-polarization quadrature amplitude modulation 16";
                    }
                    enum qam8 {
                        value "7";
                        description "quadrature amplitude modulation 8";  
                    }
                    enum dp-qam8 {
                        value "8";
                        description "dual-polarization quadrature amplitude modulation 8";  
                    }
                    enum dc-dp-qam8{
                        value "9";
                        description "DC dual-polarization quadrature amplitude modulation 8";
                    }
                }
                description "modulation format";
            }

         leaf fec {
                type enumeration {
                    enum hpdfec1 {
                      value "0";
                      description "25% SDFEC used for UTP T200.";
                    }
                    enum hpdfec2 {
                      value "1";
                      description "20% SDFEC used for UTP T200.";
                    }
                }
                description "FEC mode.";
        } 

        leaf roadm-type {
            type enumeration {
                enum CD {
                    value "0";
                    description "CD degree is applicable.";
                }
                enum AWG {
                    value "1";
                    description "AWG/DIRECT degree is applicable.";
                }
             }
            default CD;
            description "setting of ROADM type.";

        } 

        leaf confmode-type {
            type enumeration {
                enum 100GONLY {
                    value "0";
                    description "100GONLY if the ROADM systems degree, to which this PIU is connected, carries only 100G wavelengths.";
                }
                enum 10GMIX {
                    value "1";
                    description "10GMIX if the ROADM systems degree, to which this PIU is connected, carries 10G wavelengths along with 100G wavelengths.";
                    }
            }
            default 100GONLY;
            description "CNFMODE is a setting to get the best optical reach";

        }

        leaf hi-performance-fec {
            type enumeration {
                enum ON {
                    value "0";
                }
                enum OFF {
                    value "1";
                }
            }
            default OFF;
            description "hi-performance-fec is used to improve correction of received data on receiving side";         
        }

        leaf Nyquist {
            type enumeration {
                enum ON {
                    value "0";
                }
                enum OFF {
                    value "1";
                }
            }

            description "Current status of Nyquist filter mode.";
        }

        leaf direction {
            type enumeration {
                enum uni-rx {
                    value "0";
                    description "unidirectional receive only";  
                }
                enum uni-tx {
                    value "1";
                    description "unidirectional transmit only";
                }
                enum bi {
                    value "2";
                    description "bidirectional";
                }
            }
        
        }
    }


    // configuration parameters for optical transport interfaces
    augment "/if:interfaces/if:interface" {

        container otsig {
            when "../if:type = 'fjift:fujitsuOtsig'" ;

            presence "Attribute Nodes for Optical Transport Signal Group (otsig)";

            description "Optical Transport Signal Group:
                         Models the optical channel interfaces for an Optical White Box.";

            uses st:state-timer {
                refine actual-vstimer {
                    config false;
                }
            }

            uses otsig-attributes {

                refine nwrate {
                    mandatory true;
                }

                refine oper-status {
                    config false;
                }

                refine Nyquist {
                    config false;
                }

                refine subcarrier {
                    config false;
                }

            }
        }
    }

    notification otsig-notif {
        leaf name {
            type leafref {
                path "/if:interfaces/if:interface/if:name";
            }
        }

        container otsig {
            uses st:state-timer;
            uses otsig-attributes;
        }
    }
}
