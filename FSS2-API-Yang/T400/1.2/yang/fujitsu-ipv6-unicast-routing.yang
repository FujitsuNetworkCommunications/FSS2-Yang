module fujitsu-ipv6-unicast-routing {
  namespace "urn:fujitsu:params:xml:ns:yang:ietf-ipv6-unicast-routing-ext";
  prefix fujitsu-v6ur;

  import ietf-routing {
    prefix rt;
  }

  import ietf-ipv6-unicast-routing {
    prefix v6ur;
  } 

  import ietf-inet-types {
    prefix inet;
  }

  organization
    "Fujitsu Ltd.";

  contact
    "Fujitsu Ltd.

    Address: 2801 Telecom Parkway
    Richardson, Texas 75082

    Tel: +1-800-USE-FTAC (1-800-873-3822)
    Email: ftac@fnc.fujitsu.com
    Web: www.fujitsu.com/us/services/telecom";

  description
    "This file contains the extensions 
    for the ietf ipv6 unicast routing yang model.

      Copyright (c) 2016 Fujitsu Ltd.
        All rights reserved. ";

  revision 2018-01-22 {
      description "Changed filename, module name, and prefix";
  }

  revision 2017-02-21 {
      description
      "Support to have next hop address as leaf-list";
  }

  augment "/rt:routing-state/rt:routing-instance/rt:ribs/rt:rib/rt:routes/"
    + "rt:route/rt:next-hop/rt:next-hop-options/rt:simple-next-hop" {
    when "../../../rt:address-family = 'v6ur:ipv6-unicast'" {
      description
        "This augment is valid only for IPv6 unicast.";
    }
    leaf-list next-hop-address {
    type inet:ipv6-address;
    description
      "List of IPv6 next-hops.";
    } 
  }
}
