module fujitsu-subslot {
  namespace "urn:fujitsu:params:xml:ns:yang:equipment:subslot";
  prefix subslot;

  import fujitsu-physical-inventory {
    prefix physical-inventory;
  }
  import fujitsu-port {
    prefix port;
  }
  import fujitsu-entity-states {
    prefix entity-states;
  }
  import fujitsu-performance-monitoring {
    prefix pm;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains definitions for subslot equipment 
     management.
     
     Copyright (c) 2015 Fujitsu Ltd.
     All rights reserved. ";

  revision 2015-04-10 {
    description
      "Initial revision.";
  }

  grouping subslot {
    description
      "This grouping defines parameters for a subslot";
    leaf subslotID {
      type string;
      description
        "A unique subslot number";
    }
    uses entity-states:oper-status {
      when "subslotID != '0'";
      refine "oper-status" {
        config false;
      }
    }
    uses entity-states:admin-status {
      when "subslotID != '0'";
      refine "admin-status" {
        mandatory false;
        default "down";
      }
    }
    container pi {
      when "../subslotID != '0'";
      uses physical-inventory:PhysicalInventory;
      config false;
      description
        "Physical inventory information of the subslot";
    }
    uses pm:pm-info;
    list port {
      when "string-length(../../cardType) > 0";
      key "portID";
      uses port:Port;
      description
        "A list of ports per subslot identified by the 'portID'";
    }
  }
}
