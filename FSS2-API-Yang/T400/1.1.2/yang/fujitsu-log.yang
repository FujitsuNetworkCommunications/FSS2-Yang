module fujitsu-log {
  namespace "urn:fujitsu:params:xml:ns:yang:fujitsu-log";
  prefix fujitsu-log;

  import fujitsu-equipment {
    prefix eqpt;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module is used to define the RPC calls to 
       1) collect debug logs into a single file on the RAM disk
       2) display the local syslog security log contents
       3) clear the local syslog
       4) generate HW/FW version log.
     Copyright (c) 2015 Fujitsu Ltd.
     All rights reserved. ";

  revision 2017-02-06 {
    description
      "This revision adds the following RPC call:
       - trigger-tech-info";
  }
  revision 2017-01-13 {
    description
      "This revision adds the following RPC call:
       - generate-hw-version-log";
  }
  revision 2015-10-13;

  rpc create-tech-info {
    description
      "Collects all LOG data for debugging and places it in a location accessible via ftp/sftp.";
    input {
      leaf shelf-id {
        type leafref {
          path "/eqpt:eqpt/eqpt:shelf/eqpt:shelfId";
        }
        description
          "shelf ID";
      }
    }
    output {
      leaf status {
        type string {
          length "4..255";
        }
      }
    }
  }
  rpc syslog-get {
    description
      "All of syslog are displayed. ";
    input {
      leaf read-from-linenumber {
        type int32;
        mandatory true;
      }
      leaf num-of-lines {
        type int32;
        mandatory true;
      }
    }
    output {
      leaf-list status {
        type string {
          length "1..max";
        }
        description
          "All of syslog are displayed.
           (It is likely to become a multi-line. )";
      }
      leaf total-num-of-lines {
        type string;
        description
          "Total Number of lines in syslog";
      }
    }
  }
  rpc clear-syslog {
    description
      "Syslog is cleared. ";
    output {
      leaf status {
        type string {
          length "1..max";
        }
        description
          "response of command";
      }
    }
  }
  rpc security-log-get {
    description
      "All of security-log are displayed. However, there is an execution authority limit. ";
    input {
      leaf read-from-linenumber {
        type int32;
        mandatory true;
      }
      leaf num-of-lines {
        type int32;
        mandatory true;
      }
    }
    output {
      leaf-list status {
        type string {
          length "1..max";
        }
        description
          "All of security-log are displayed.
           (It is likely to become a multi-line. )";
      }
    }
  }

  typedef date-time {
    type string {
      pattern "\\d{4}-\\d{2}-\\d{2}(T\\d{2}:\\d{2}:\\d{2})?";
    }
    description
      "Date with optional local time. YYYY-MM-DD[THH:MM:SS]";
  }

  rpc swerr-log-get {
    description
      "Display swerr log content.";
    input {
      leaf shelf-id {
        type leafref {
          path "/eqpt:eqpt/eqpt:shelf/eqpt:shelfId";
        }
        description
          "shelf ID";
      }
      leaf slot {
        type uint32;
        description
          "Display swerrs from specified slot. Default: 0";
        default "0";
      }
      choice filter {
        case time {
          leaf from {
            type date-time;
            description
              "Display swerrs from timestamp(YYYY-MM-DD[THH:MM:SS])";
          }
          leaf to {
            type date-time;
            description
              "Display swerrs till timestamp(YYYY-MM-DD[THH:MM:SS])";
          }
          leaf count {
            type uint32 {
              range "1..max";
            }
            description
              "Display upto specified number of swerrs";
          }
        }
        case number-first {
          leaf first {
            type uint32;
            description
              "Display upto first specified number of swerrs";
          }
        }
        case number-last {
          leaf last {
            type uint32;
            description
              "Display upto last specified number of swerrs";
          }
        }
      }
    }
    output {
      leaf-list status {
        type string;
      }
    }
  }
  rpc generate-hw-version-log {
    description
      "Generate HW/FW version log.";
    input {
      leaf shelf-id {
        type leafref {
          path "/eqpt:eqpt/eqpt:shelf/eqpt:shelfId";
        }
        description
          "shelf ID";
      }
    }
    output {
      leaf status {
        type string {
          length "4..255";
        }
      }
    }
  }

  grouping eqpt-id {
    leaf shelf-id {
      type leafref {
        path "/eqpt:eqpt/eqpt:shelf/eqpt:shelfId";
      }
      mandatory true;
      description
        "shelf ID";
    }
    leaf slot-id {
      type leafref {
        path "/eqpt:eqpt/eqpt:shelf/eqpt:slot/eqpt:slotID";
      }
      description
        "slot ID";
    }
  }

  typedef logType {
    type enumeration {
      enum "MBLOG" {
        value 0;
        description
          "MB Log";
      }
    }
  }

  rpc trigger-tech-info {
    description
      "Triggers generation of ON-Demand Log data";
    input {
      uses eqpt-id;
      leaf trigger {
        type logType;
        mandatory true;
        description
          "Log Type";
      }
    }
    output {
      leaf status {
        type string {
          length "4..255";
        }
      }
    }
  }
}
