module fujitsu-user-security-dev.prod {
  yang-version 1;
  namespace "urn:fujitsu:params:xml:ns:yang:user-security-dev.prod";
  prefix user-security-dev.prod;

  import fujitsu-user-security {
    prefix fuser;
  }

  organization
       "Fujitsu Ltd.";

  contact
       "Fujitsu Ltd.

        Address: 2801 Telecom Parkway
                 Richardson, Texas 75082

        Tel: +1-800-USE-FTAC (1-800-873-3822)
        Email: ftac@fnc.fujitsu.com
        Web: www.fujitsu.com/us/services/telecom";

  description
       "This module is used to remove speciific user security defaults and systemwide
        leafs based on security features that are not supported on a specific product. 
        Copyright (c) 2015 Fujitsu Ltd.
        All rights reserved. ";

  revision 2015-10-27 {
    description
    "Update max elements in authentication-order to 2 for RADIUS";
  }

  revision 2015-10-27;

  // This particular deviations file is for T-Series R1.1

  /* SW Dev supports "symlink feature" idle-timeout is set via 
     tailf-aaa user container as follows:
       set user <username> session idle-timeout <value> */
  deviation /fuser:usersec/fuser:idle-timeout {
    deviate not-supported;
  }

  deviation /fuser:security/fuser:systemwide/fuser:authentication-order {
    deviate replace {
       max-elements 2;
    }
  } 
}
