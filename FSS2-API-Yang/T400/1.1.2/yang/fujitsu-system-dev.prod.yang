module fujitsu-system-dev.prod {
    namespace "urn:fujitsu:params:xml:ns:yang:system-dev.prod";
    prefix fujitsu-system-dev.prod;

    import fujitsu-system {
        prefix system;
    }

    organization
       "Fujitsu Ltd.";

    contact
       "Fujitsu Ltd.

        Address: 2801 Telecom Parkway
                 Richardson, Texas 75082

        Tel: +1-800-USE-FTAC (1-800-873-3822)
        Email: ftac@fnc.fujitsu.com
        Web: www.fujitsu.com/us/services/telecom";

    description
       "This module contains the fujitsu system releated deviations,

        Copyright (c) 2017 Fujitsu Ltd.
        All rights reserved. ";

    revision 2017-02-03 {
        description
        " - Removed deviation added to allow only warm reboot
          - Cold re-start is supported for BDC2-C202";
    }

    deviation "/system:init-filter-timer" {

       deviate not-supported;
    }
}
