module fujitsu-file-transfer-webui {
  namespace "urn:fujitsu:params:xml:ns:yang:ftp-webui";
  prefix ftxr-webui;

  import ietf-inet-types {
    prefix inet;
  }

  rpc transfer {
    description
      "File transfer using FTP/SFTP";
    input {
      choice trans-method {
        mandatory true;
        leaf sftp {
          description
            "Transfer mode is SFTP.";
          type empty;
        }
        leaf ftp {
          description
            "Transfer mode is FTP.";
          type empty;
        }
      }
      leaf action {
        mandatory true;
        description
          "Type of action - download/upload.";
        type enumeration {
          enum "upload" {
            description
              "Specify the upload action. The server sends
               the file identified by the local-file-path
               to the remote-file-path.";
          }
          enum "download" {
            description
              "Specify the download action. The server retrieves
               the file identified by the remote-file-path
               to the local-file-path.";
          }
        }
      }
      leaf local-file-path {
        type string;
        mandatory true;
        description
          "Local file path.
           Ex: /var/shared/example.txt";
      }
      leaf remote-file-path {
        type inet:uri;
        description
          "Remote file path. 
           A URI for the remote file path. This can be a URI of
           type FTP/SFTP, depending on the protocol
           which is being used for the transfer. 
           
           Format://user[:password]@host[:port]/path. 
           Ex: 
           IPv4: //test:verify@167.254.211.116:21/home/user/sample
           IPv6: //test:verify@[2001:db8:0:1::10]:22/home/user/sample";
      }
    }
    output {
      leaf status {
        type string;
        description
          "Status of the file transfer operation";
      }
    }
  }
}
