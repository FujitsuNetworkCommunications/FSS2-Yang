module fujitsu-subport {
  namespace "urn:fujitsu:params:xml:ns:yang:equipment:subport";
  prefix subport;

  import fujitsu-performance-monitoring {
    prefix pm;
  }
  import fujitsu-entity-states {
    prefix entity-states;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module contains definitions for Pluggable equipment 
     management.
     
     Copyright (c) 2015 Fujitsu Ltd.
     All rights reserved. ";

  revision 2015-09-25 {
    description
      "Initial revision.";
  }

  grouping subPort {
    description
      "subport on the port";
    leaf subPortID {
      type string;
      description
        "subport identifier";
    }
    list xconRef {
      key "xconID";
      max-elements "2";
      leaf xconID {
        type string;
        description
          "och connection id";
      }
      leaf srcOch {
        type string;
        description
          "src och aid";
      }
      leaf dstOch {
        type string;
        description
          "dst och aid";
      }
    }
    uses pm:pm-info;
    uses entity-states:oper-status {
      refine "oper-status" {
        config false;
      }
    }
    uses entity-states:admin-status {
      refine "admin-status" {
        mandatory false;
        default "down";
      }
    }
  }
}
