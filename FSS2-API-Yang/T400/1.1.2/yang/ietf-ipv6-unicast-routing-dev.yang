module ietf-ipv6-unicast-routing-dev {

  namespace "urn:fujitsu:params:xml:ns:yang:ietf-ipv6-unicast-routing-dev";

  prefix "v6ur-dev";

  import ietf-routing {
      prefix rt;
  }

  import ietf-ipv6-unicast-routing {
    prefix "v6ur";
  }

  // Support up to 32 ipv6 static routes per requirement of L100/T200 Release 1
  deviation "/rt:routing/rt:routing-instance/rt:routing-protocols/"
        + "rt:routing-protocol/rt:static-routes/v6ur:ipv6/v6ur:route" {
    deviate add {
      max-elements 32;
    }
  }

  deviation "/rt:fib-route/rt:input/rt:destination-address/v6ur:address"  {
    deviate not-supported;
  }

  deviation "/rt:fib-route/rt:output/rt:route/v6ur:destination-prefix" {
    deviate not-supported;
  }

  deviation "/rt:fib-route/rt:output/rt:route/rt:next-hop/rt:next-hop-options/rt:simple-next-hop/v6ur:next-hop-address" {
    deviate not-supported;
  }

}
