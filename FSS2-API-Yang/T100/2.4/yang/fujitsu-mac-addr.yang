module fujitsu-mac-addr {
  namespace "urn:fujitsu:params:xml:ns:yang:fujitsu-mac-addr";
  prefix fujitsu-mac-addr;

  import ietf-yang-types {
    prefix yang;
  }
  import fujitsu-equipment {
    prefix eqpt;
  }

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "MAC address of slot and subslot.
     
     Copyright (c) 2016 Fujitsu Ltd.
     All rights reserved. ";

  revision 2016-02-01 {
    description
      "Initial revision.";
  }

  augment "/eqpt:eqpt/eqpt:shelf/eqpt:slot" {
    leaf mac-address-max {
      type yang:mac-address;
      default "00:00:00:00:00:00";
      config false;
      description
        "Maximum value of MAC-address\n";
    }
    leaf mac-address-min {
      type yang:mac-address;
      default "00:00:00:00:00:00";
      config false;
      description
        "Minimum value of MAC-address\n";
    }
  }
  augment "/eqpt:eqpt/eqpt:shelf/eqpt:slot/eqpt:subslot" {
    leaf mac-address-max {
      type yang:mac-address;
      default "00:00:00:00:00:00";
      config false;
      description
        "Maximum value of MAC-address\n";
    }
    leaf mac-address-min {
      type yang:mac-address;
      default "00:00:00:00:00:00";
      config false;
      description
        "Minimum value of MAC-address\n";
    }
  }
}
