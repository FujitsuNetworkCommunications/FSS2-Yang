module fujitsu-ssh-host-key {
  yang-version 1;
  namespace "urn:fujitsu:params:xml:ns:yang:typedef:ssh-host-key";
  prefix hkey;

  organization
    "Fujitsu Ltd.";
  contact
    "Fujitsu Ltd.
     
     Address: 2801 Telecom Parkway
              Richardson, Texas 75082
     
     Tel: +1-800-USE-FTAC (1-800-873-3822)
     Email: ftac@fnc.fujitsu.com
     Web: www.fujitsu.com/us/services/telecom";
  description
    "This module is used to define the RPC call to create a SSH Host Key,
     provide a notification of when the creation is complete, and support
     retrieval of the Host key fingerprint. 
     Copyright (c) 2015 Fujitsu Ltd.
     All rights reserved. ";

  revision 2015-10-14;

  rpc generate-ssh-host-key {
    output {
      leaf begin-generation {
        type string;
        description
          "Returned immediately to indicate host key
           generation has begun.";
      }
    }
  }
  rpc show-ssh-host-key {
    output {
      leaf status {
        type string;
        description
          "Status of host key. For example: 
           'Host Key Generation is in progress' or 
           'Host Key Generation Complete' and include a date-time string.";
      }
      leaf fingerprint {
        type string;
        description
          "Fingerprint of Host key (once generated). 
           Should be blank while generation is in progress.";
      }
    }
  }
  notification ssh-host-key-generation-complete {
    leaf status {
      type string;
    }
    leaf fingerprint {
      type string;
    }
    description
      "SSH Host Key generation completed.";
  }
}
